Sub Main()

	SharedVariable("LogVar") = "TAIT Title Page View Scale"
	iLogicVB.RunExternalRule("Write SV to Log.iLogicVB")
	
	'Try
	Dim oDoc as DrawingDocument = ThisApplication.ActiveDocument
	Dim oSheets as Sheets = oDoc.Sheets
	Dim shtTitle as Sheet = oSheets.Item(1)
	
	If shtTitle.DrawingViews.Count > 0 Then
		Dim oOverview as DrawingView = shtTitle.DrawingViews.Item(1)

		ViewPlaceH = (shtTitle.Width * 0.66) + (Parameter("HOverview")*2.54)
		ViewPlaceV = (shtTitle.Height * 0.33) + (Parameter("VOverview")*2.54)

		Dim oViewCenter as Point2d = ThisApplication.TransientGeometry.CreatePoint2d(ViewPlaceH, ViewPlaceV)
		oOverview.Center = oViewCenter
		oOverview.Scale = 1
		oOverview.Scale = 5*2.54 / oOverview.Height
	End If
	
End Sub
