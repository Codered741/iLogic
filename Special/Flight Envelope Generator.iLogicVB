AddReference "Microsoft.Office.Interop.Excel"
Imports System.Windows.Forms

Sub Main()

	SharedVariable("LogVar") = "Special - Flight Envelope Generator"
	iLogicVB.RunExternalRule("Write SV to Log.iLogicVB")
	
	'On Error Resume Next
	Dim oDoc As PartDocument = ThisApplication.ActiveDocument
	Dim oCompDef As PartComponentDefinition = oDoc.ComponentDefinition
	Dim oSks3d As Sketches3D = oCompDef.Sketches3D
	Dim oSk3d As Sketch3d
	Dim oSplines3d As SketchSplines3D
	Dim oSpline3d As SketchSpline3D
	Dim Runtime As String = Now.ToString("yyyyMMddTHHmm")
	Dim SketchName As String = "Envelope Control Sketch " & Runtime
	
	SharedVariable("LogVar") = "Flight Envelope Generator"
	iLogicVb.RunExternalRule("Write SV to Log.iLogicVB")
	
	'get/create excel
	Dim xlApp As Microsoft.Office.Interop.Excel.Application
	Dim xlOpenedByRule As Boolean = False
	Try
		xlApp = GetObject(, "Excel.Application")
	Catch 'If Err.Number <> 0 Then
		Err.Clear
		'msgbox("Opening Excel...")
		xlApp = CreateObject("Excel.Application")
		xlOpenedByRule = True
		xlApp.Visible  = True
		' If Err.Number <> 0 Then	
			' MsgBox("Cannot access Excel")
			' Exit Sub	
		' End If
	End Try 'End If
	
	'Prompt User to select Excel file
	Dim WbName As String = ChooseXlFile("c:\")
	
	'Handle possible error from function
	If WbName = "" Then
		MsgBox("File was not found.  Please try again")
		Exit Sub
	End If
	
	'Crete points for spline
	Dim oTG As TransientGeometry = ThisApplication.TransientGeometry
	Dim oFitPoints as ObjectCollection = ThisApplication.TransientObjects.CreateObjectCollection
	Dim oSplines as ObjectCollection = ThisApplication.TransientObjects.CreateObjectCollection
	
	'Open the workbook and get the sheet
	Dim wb As Microsoft.Office.Interop.Excel.Workbook = xlApp.Workbooks.Open(WbName, True, False)
	If Err.Number <> 0 Then
		Err.Clear
		MsgBox("Error Opening Excel")
		xlApp.Close(False)
		Exit Sub
	End If
	
	Dim ws as Microsoft.Office.Interop.Excel.Worksheet
	Dim wsRaw As Microsoft.Office.Interop.Excel.Worksheet
	Dim SheetName As New List(Of String)
	
	'determine if multiple sheets exist, allow user to select sheet, if more than one.  
	If wb.Worksheets.Count > 1 Then
		For Each sht In wb.Worksheets
			SheetName.Add(sht.Name)
		Next
		ws = wb.Worksheets.Item(InputListBox("Please select a sheet. ", SheetName, SheetName(1), "Sheet Select"))
	Else
		ws = wb.Worksheets.Item(1)
	End If
	
	'Start reading in the values
	Dim Row As Integer = 1
	Dim Yval As Double '= ws.Cells(1, 2).Value
	Dim Xval As Double
	Dim Zval As Double
	
	
	'Define the beginning of the data in the sheet. 
	Dim StartRow As Integer = 2
	Dim StartCol as Integer = 5
	Dim EndRow As Integer = 52
	Dim EndCol as Integer = 55
	Dim XIndexRow As Integer = 1
	Dim YIndexCol as Integer = 4
	
	Dim CurYval As Double
	Dim CurXval as Double
	Dim CurZval as Double
	
	Dim DestRow As Integer = 1
	Dim rCurRow As Integer
	Dim rCurCol As Integer
	
	Dim oWPs = oCompDef.WorkPoints
	
	wp1 = oWPs.AddFixed(oTG.CreatePoint(ws.Cells(2,2).Value * 30.48, ws.Cells(3,2).Value * 30.48, ws.Cells(4, 2).Value * 30.48))
	wp2 = oWPs.AddFixed(oTG.CreatePoint(ws.Cells(7,2).Value * 30.48, ws.Cells(8,2).Value * 30.48, ws.Cells(9, 2).Value * 30.48))
	wp3 = oWPs.AddFixed(oTG.CreatePoint(ws.Cells(12,2).Value * 30.48, ws.Cells(13,2).Value * 30.48, ws.Cells(14, 2).Value * 30.48))
	wp4 = oWPs.AddFixed(oTG.CreatePoint(ws.Cells(17,2).Value * 30.48, ws.Cells(18,2).Value * 30.48, ws.Cells(19, 2).Value * 30.48))
	
	wp1.Name = "1st Point " & Runtime
	wp2.Name = "2nd Point " & Runtime
	wp3.Name = "3rd Point " & Runtime
	wp4.Name = "4th Point " & Runtime
	
	Dim SketchCount As Integer = 1
	
	SetOrientationAcad()
	
	SetCameraIso()
	
	'iterate through all the rows of the table
	For rCurRow = StartRow To EndRow
		
		'Create Sketch
		oSk3d = oSks3d.Add() 'create a 3d sketch
		oSk3d.Name = SketchName & " - " & SketchCount
		oSplines3d = oSk3d.SketchSplines3D
		
		'Iterate through all the columns 
		For rCurCol = StartCol To EndCol
			If String.IsNullOrEmpty(ws.Cells(rCurRow, rCurCol).Value) = False 'check if Z value has something
				Yval = ws.Cells(rCurRow, YIndexCol).Value 'read the Y value from the index column
				Xval = ws.Cells(XIndexRow, rCurCol).Value 'read the Xvalue from the top row
				Zval = ws.Cells(rCurRow, rCurCol).Value 'read the Z value from the grid
				
				oFitPoints.Add(oTG.CreatePoint(Xval * 30.48 , Yval * 30.48 , Zval * 30.48 ))
				
				If rCurCol = EndCol Then
					If oFitPoints.Count > 1 Then
						oSpline3d = oSplines3d.Add(oFitPoints, 26369)
						oFitPoints.Clear
						oSplines.Add(oSk3d.Profiles3D.AddOpen)
						SketchCount = SketchCount + 1
					Else
						oFitPoints.Clear
						oSk3d.Delete
					End If
				End If
			Else 
				If rCurCol = EndCol Then
					If oFitPoints.Count > 1 Then
						oSpline3d = oSplines3d.Add(oFitPoints, 26369)
						oFitPoints.Clear
						oSplines.Add(oSk3d.Profiles3D.AddOpen)
						SketchCount = SketchCount + 1
					Else 
						oFitPoints.Clear
						oSk3d.Delete
					End If
				End If
			End If
		Next
	Next	
	
	uCreateLoft = MessageBox.Show("Do you want to create a solid from this data?", "Create Solid Body?", MessageBoxButtons.YesNo)
	
	If oSplines.Count > 2 AndAlso uCreateLoft = vbYes Then
		oLoftDef = oCompDef.Features.LoftFeatures.CreateLoftDefinition(oSplines, kSurfaceOperation)	
		oLoft = oCompDef.Features.LoftFeatures.Add(oLoftDef)
		oLoft.Name = "Envelope Control Surface " & Runtime
		
		' If Err.Number <> 0 Then
			' MsgBox("An error occurred in loft creation.  " & vbLf & Err.Number & " - " & Err.Description)
		' End If
		
		CreateSolid(oDoc, oCompDef, Runtime)
	
		SetCameraIso()
	Else 
		MessageBox.Show("There is not enough data to continue.  ", "Insufficient Data", MessageBoxButtons.OK)
		Goto quit
	End If
  

	
	quit:
	
	wb.Close(True) 
	
	If openedByRule = True
		xlApp.Quit
	End If
End Sub 'Main

Function ChooseXlFile(InitialDirectory As String) As String
    Dim SelectedFile As String
    Dim openFileDialog1 As New OpenFileDialog()

    openFileDialog1.InitialDirectory = InitialDirectory
    openFileDialog1.Filter = "Excel files (*.xls;*.xlsx)|*.xls;*.xlsx"
    openFileDialog1.FilterIndex = 1
    openFileDialog1.RestoreDirectory = False

    If openFileDialog1.ShowDialog() = System.Windows.Forms.DialogResult.OK Then
		Return openFileDialog1.FileName
        ' Try
            ' myStream = openFileDialog1.OpenFile()
            ' If (myStream IsNot Nothing) Then
				' Return myStream
            ' End If
        ' Catch Ex As Exception
            ' MessageBox.Show("Cannot read file from disk. Original error: " & Ex.Message)
        ' Finally
            ' ' Check this again, since we need to make sure we didn't throw an exception on open.
            ' If (myStream IsNot Nothing) Then
                ' myStream.Close()
            ' End If
        ' End Try
	Else 
		Return ""
    End If
End Function

Sub CreateSolid(oDoc as Document, oCompDef As ComponentDefinition, Runtime As String)

	Dim oFootSketch As Inventor.PlanarSketch
	oFootSketch = oCompDef.Sketches.Add(oCompDef.WorkPlanes("XY Plane"), False)
	oFootSketch.Name = "Envelope Footprint Sketch"
	Dim oLoftBody = oCompDef.WorkSurfaces.Item(1).SurfaceBodies.Item(1)
	
	For Each oEdge As Inventor.Edge In oLoftBody.Edges
		oFootSketch.AddByProjectingEntity(oEdge)
	Next
	
	Dim oProfile As Inventor.Profile = oFootSketch.Profiles.AddForSolid
	
	Dim oExtDef as Inventor.ExtrudeDefinition = oCompDef.Features.ExtrudeFeatures.CreateExtrudeDefinition(oProfile, kNewBodyOperation)
	
	oExtDef.SetToExtent(oLoftBody.Faces.Item(1))
	
	oExt = oCompDef.Features.ExtrudeFeatures.Add(oExtDef)
	
	oExt.Name =  "Flight Envelope " & Runtime
	
	oLoftBody.Visible = False
	
End Sub 'CreateSolid

Sub SetCameraIso()
	'ThisApplication.CommandManager.ControlDefinitions.Item("AppZoomAllCmd").Execute
	Dim oCam As Camera = ThisApplication.ActiveView.Camera
	oCam.ViewOrientationType = 10759
	oCam.Fit()
	oCam.Apply
End Sub 'SetCameraIso

Sub SetOrientationAcad()
	Dim oView As Inventor.View = ThisApplication.ActiveView
	Dim oCam as Inventor.Camera = oView.Camera
	oView.ResetFront
	oCam.ViewOrientationType = 10757 'kBottomViewOrientation
	oCam.Fit()
	oCam.ApplyWithoutTransition
	oView.SetCurrentAsFront
	
	oCam.ViewOrientationType = 10759 'kIsoTopRightViewOrientation
	oCam.Fit()
	oCam.ApplyWithoutTransition
	oView.SetCurrentAsHome
End Sub 'SetOrientationAcad
