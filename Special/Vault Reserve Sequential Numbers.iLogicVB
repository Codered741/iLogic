AddReference "Autodesk.Connectivity.WebServices"
AddReference "Autodesk.DataManagement.Client.Framework.Forms"
AddReference "Autodesk.DataManagement.Client.Framework.Vault"
AddReference "Autodesk.DataManagement.Client.Framework.Vault.Forms"
AddReference "Connectivity.InventorAddin.EdmAddin"

Imports ACW = Autodesk.Connectivity.WebServices
Imports VDF = Autodesk.DataManagement.Client.Framework
Imports Autodesk.DataManagement.Client.Framework.Vault.Services
Imports Autodesk.DataManagement.Client.Framework.Vault.Currency.Connections
Imports edm = Connectivity.InventorAddin.EdmAddin
Imports System.Collections.Generic
Imports My.Computer.FileSystem

Sub Main()
    ' Prompt for scheme name 
    Dim schemeName As String = "Sequence" 'InputBox("Enter the Vault numbering scheme name:", "Numbering Scheme", "DefaultScheme")
    If String.IsNullOrEmpty(schemeName) Then Exit Sub ' Cancel if empty
    
    ' Prompt for number of files
    Dim inputNum As String = InputBox("Enter the number of file numbers to generate:", "Quantity", "1")
    Dim numFiles As Integer
    If Not Integer.TryParse(inputNum, numFiles) OrElse numFiles <= 0 Then
        MessageBox.Show("Invalid number entered. Exiting.", "Error")
        Exit Sub
    End If
    
    ' Generate and display
    Dim generatedNumbers As List(Of String) = getFilenamesFromVaultNamingScheme(schemeName, "", numFiles)
	Dim copyText as String = ""
	For each num In generatedNumbers
		If Not num = inputNum Then
			copyText = copyText & num & vbCr
		Else
			copyText = copyText & num
		End if
	Next
	
	My.Computer.Clipboard.SetText(copyText)
	
    If generatedNumbers IsNot Nothing AndAlso generatedNumbers.Count > 0 Then
        Dim output As String = "Generated " & generatedNumbers.Count & " numbers:" & Environment.NewLine & String.Join(Environment.NewLine, generatedNumbers)
        MessageBox.Show("Success! Numbers have been copied to your clipboard.  ","Success", MessageBoxButtons.OK, MessageBoxIcon.Information)
		
	
		
    End If
End Sub

Public Function getFilenamesFromVaultNamingScheme(RequiredSchemeName As String, RequiredSchemeString As String, numberOfNames As Integer) As List(Of String)
    Dim numbers As New List(Of String)
    Dim Connection As VDF.Vault.Currency.Connections.Connection = edm.EdmSecurity.Instance.VaultConnection()
    If Connection Is Nothing Then
        MessageBox.Show("No Vault connection detected. Please log in to Vault.", "Error", MessageBoxButtons.OK, MessageBoxIcon.Error)
        Return Nothing
    End If
    
    Try
        Dim entityClassId = VDF.Vault.Currency.Entities.EntityClassIds.Files
        Dim numSchemes As ACW.NumSchm() = Connection.WebServiceManager.NumberingService.GetNumberingSchemes(entityClassId, Nothing)
        Dim requiredScheme As ACW.NumSchm = (From sch As ACW.NumSchm In numSchemes Where sch.Name = RequiredSchemeName Select sch).FirstOrDefault()
        
        If requiredScheme Is Nothing Then
            MessageBox.Show("Numbering scheme '" & RequiredSchemeName & "' not found.", "Error", MessageBoxButtons.OK, MessageBoxIcon.Error)
            Return Nothing
        End If
        
        Dim numGenArgs() As String = {RequiredSchemeString}
        For i As Integer = 1 To numberOfNames
            Dim genNum As String = Connection.WebServiceManager.DocumentService.GenerateFileNumber(requiredScheme.SchmID, numGenArgs)
            numbers.Add(genNum)
        Next
        
        Return numbers
    Catch ex As Exception
        MessageBox.Show("Error generating numbers: " & ex.Message, "Error", MessageBoxButtons.OK, MessageBoxIcon.Error)
        Return Nothing
    End Try
End Function
