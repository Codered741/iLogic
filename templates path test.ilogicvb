Imports System.IO
Imports System.Text

Sub Main()
	MessageBox.Show(getTemplatesFolderPath(), "Path")
End Sub

Function getTemplatesFolderPath ()
	
	Dim invTempLoc as String = "C:\_vaultWIP\inv_Templates_Path.txt"
	
	If File.Exists(invTempLoc)
		Dim oRead as new StreamReader(invTempLoc)
	
		Try 
			return oRead.ReadLine()
		Catch
			return 0
		End Try
		
	Else
		MessageBox.Show("The file could not be found. Please 'Get","File Not Found", MessageBoxButtons.OK, MessageBoxIcon.Error)
		return 0
	End if
	
End Function
