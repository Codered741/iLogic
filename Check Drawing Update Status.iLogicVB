Imports System 
Imports System.IO
Imports System.IO.File
Imports System.Text

Sub Main()
	
	'SharedVariable.RemoveAll()
	
	' Dim usrLatestAck = MessageBox.Show("Please ensure that you have the latest drawings of this assembly.  "  _
		' & vbLf & "Contact #des_inventor for assistance.  ", "Latest Drawing Warning", MessageBoxButtons.OKCancel, MessageBoxIcon.Warning)
		
	' If usrLatestAck = vbCancel Then	
		' Exit Sub
	' End If
	
	Dim oDoc as Document = ThisApplication.ActiveDocument
	Dim FileNameMinLong as Integer = 21 'c:/_vaultWIP/Designs/ is 21 characters.  
	
	iLogicForm.CloseGlobal("General Utilities")
	iLogicForm.CloseGlobal("Smart Part Config")
	iLogicForm.CloseGlobal("Epicor Job Config")
	
	'check if active document is an assembly
	If isAsm(oDoc) = False
		MsgBox("Please run from an Assembly")
		Return
	End If
	
	'write to iLogic Log
	SharedVariable("LogVar") = "Check Drawing Status" 
	iLogicVB.RunExternalRule("Write SV to Log.iLogicVB")
	
	Dim lstDrawings as New List(of String)
	
	Dim BOMDocs As New List(of String)

	'get list of part numbers from Structured BOM
	GetDocsFromBOM(oDoc, BOMDocs)
	
	
	 Dim oProgressBar as Inventor.ProgressBar
	 oProgressBar = ThisApplication.CreateProgressBar(False, BOMDocs.Count, "Finding Drawings...")

	'Attempt to find a drawing file of the same name as the assembly doc
	RefDwgFullFileName = FindDrawingFilePN(oDoc)
	
	oProgressBar.Message = "Checking for drawing of " & oDoc.FullFileName
	oProgressBar.UpdateProgress
	
	Dim ModelFileInfo = My.Computer.FileSystem.GetFileInfo(oDoc.FullFileName)
	Dim ModelAccTime As DateTime = ModelFileInfo.LastWriteTime
	
	Dim RefFileInfo
	Dim RefAccTime As DateTime
	
	
	
	If RefDwgFullFileName.Length > FileNameMinLong Then 
	
		RefFileInfo = My.Computer.FileSystem.GetFileInfo(RefDwgFullFileName)
		RefAccTime = RefFileInfo.LastWriteTime
		
		If DateTime.Compare(RefAccTime, ModelAccTime) < 0 Then
	
			lstDrawings.Add(RefDwgFullFileName)
			
		End If
		
	End If
	
	
	'Dim bDoc as Document
	For Each BOMDoc as String In BOMDocs
		bDoc = ThisApplication.Documents.ItemByName(BOMDoc) 'convert full file name to document object
		
		oProgressBar.Message = "Checking for drawing of " & BOMDoc 'oRefDoc.FullFileName
		oProgressBar.UpdateProgress
		
		'Attempt to find a drawing file of the same name as the model doc
		RefDwgFullFileName = FindDrawingFilePN(bDoc)
		
		ModelFileInfo = My.Computer.FileSystem.GetFileInfo(BOMDoc)
		ModelAccTime = ModelFileInfo.LastWriteTime
		
		If RefDwgFullFileName.Length > FileNameMinLong Then 
		
			RefFileInfo = My.Computer.FileSystem.GetFileInfo(RefDwgFullFileName)
			RefAccTime = RefFileInfo.LastWriteTime
			
			If DateTime.Compare (RefAccTime, ModelAccTime) < 0 Then
				lstDrawings.Add(RefDwgFullFileName)
			End If				
			
		End If
		
	Next
	
	oProgressBar.Close		
	Try 
		SVal = SharedVariable("BatchPlotInvoke")
	Catch 
		SharedVariable("BatchPlotInvoke") = False
	End Try

	If lstDrawings.Count > 0 Then
	
		If SharedVariable("BatchPlotInvoke") = False
			usrOpenDwgs = MessageBox.Show(lstDrawings.Count & " drawings were found that appear to be out of date.  Would you like to open them?", "Drawing Update Check", MessageBoxButtons.YesNo, MessageBoxIcon.Question)
			oCommandMgr = ThisApplication.CommandManager
			
		Else
			MessageBox.Show(lstDrawings.Count & " drawings were found that appear to be out of date. ", "Drawing Update Check", MessageBoxButtons.OK, MessageBoxIcon.Question)
			usrOpenDwgs = vbNo
		End If
		
		If usrOpenDwgs = vbYes Then
			usrCloseDwgs = MessageBox.Show("Would you like to to automatically update and close the drawings WITHOUT checking them?", "Drawing Update Check", MessageBoxButtons.YesNo, MessageBoxIcon.Question)
				Dim oOptions as NameValueMap = ThisApplication.TransientObjects.CreateNameValueMap
				oOptions.Value("DeferUpdates") = False
				oOptions.Value("FastOpen") = False
				
				For Each Dwg in lstDrawings
					dwgDoc = ThisApplication.Documents.OpenWithOptions(Dwg, oOptions, True)
					If usrCloseDwgs = vbYes Then
						'CommandManager VaultCheckoutTop
						oCommandMgr.ControlDefinitions.Item("VaultCheckout").Execute
						'Update Drawing
						dwgDoc.Update
						dwgDoc.Sheets.Item(1).Activate
						Try 
							dwgDoc.Save
						Catch 
							MessageBox.Show("Unable to save the drawing " & dwg & " This drawing will remain open for manual update and saving.  ", "File Save Error", MessageBoxButtons.OK, MessageBoxIcon.Warning)
							Goto FSErr
						End Try
						'CommandManager VaultCheckIn
						oCommandMgr.ControlDefinitions.Item("VaultCheckIn").Execute'2(false)
						'System.Windows.Forms.SendKeys.SendWait(Chr(9) & vbCrLf)
						dwgDoc.Close(false)	
	FSErr:						
					End If
				Next
			
		End If
	Else 
		MessageBox.Show("No Drawings were found to be out of date.  Congrats!!!", "Drawing Update Check", MessageBoxButtons.OK)
	End If

	
End Sub 'Main

Sub GetDocsFromBOM(oDoc as Document, ByRef BOMDocs as List(of String))
	
	If oDoc.DocumentType <> kAssemblyDocumentObject Then
		MsgBox("This rule can only be run from an assembly")
		Exit Sub
	End If
	
	Dim oDocBOM As BOM = oDoc.ComponentDefinition.BOM

	oDocBOM.StructuredViewEnabled = True
	oDocBOM.StructuredViewFirstLevelOnly = False
	oDocBOM.PartsOnlyViewEnabled = False
	
	Dim oBOMView as BOMView = oDocBOM.BOMViews.Item("Structured")	
	Dim oBOMRows As BOMRowsEnumerator = oBOMView.BOMRows
	'Dim oCompDef As ComponentDefinition
	'Dim oPNProp as Inventor.Property
	
	For Each oRow as BOMRow in oBOMRows
		
		GetBOMRowDocFile(oRow, BOMDocs)
		
	Next 
	
	'BOMDocs.Sort()
	
End Sub

Sub GetBOMRowDocFile(oRow as BOMRow, ByRef BOMDocs as List(of String))
	
	Dim oCompDef As ComponentDefinition
	
	'Add the part number of the current row, for parts that have children
	oCompDef = oRow.ComponentDefinitions.Item(1)
	
	If oCompDef.Type = 100675072 Then 'exclude Virtual Components
		'do nothing
	Else

		DocName = oCompDef.Document.FullFileName

		If Not BOMDocs.Contains(DocName) Then
			BOMDocs.Add(DocName)
		End If
		
	End If
		
	If Not oRow.ChildRows Is Nothing Then
	
		If Not BOMDocs.Contains(DocName) Then
			BOMDocs.Add(DocName)
		End If
	
		For Each oChildRow as BOMRow in oRow.ChildRows		
			GetBOMRowDocFile(oChildRow, BOMDocs)
		Next
		
	End If
	
End Sub

Function FindDrawingFilePN(PartOrAssemblyDoc As Document) As String
    Dim fullFilenamePN As String
    fullFilenamePN = PartOrAssemblyDoc.fullFilename
   
    ' Extract the path from the full filename.
    Dim path As String = ThisApplication.DesignProjectManager.ActiveDesignProject.WorkspacePath
    'path = Left$(fullFilenamePN, InStrRev(fullFilenamePN, "\"))

	Dim iProps as PropertySet = PartOrAssemblyDoc.PropertySets.Item("Design Tracking Properties")
	Dim pn = iProps.Item("Part Number")
	
    Dim filename As String = pn.Value

    ' Find if the drawing exists.
    Dim drawingFilename As String
    drawingFilename = ThisApplication.DesignProjectManager.ResolveFile(path, filename & ".dwg")
   
    ' Check the result.
    If drawingFilename = "" Then
       
        ' Find if the drawing exists.
        drawingFilename = ThisApplication.DesignProjectManager.ResolveFile(path, filename & ".idw")
   
        ' Return the result.
        If drawingFilename <> "" Then
            Return drawingFilename
        Else
            Return ""
        End If
    Else
        ' Return the result.
         Return drawingFilename
    End If
End Function 'FindDrawingFilePNN

Function DocumentFileName(Doc As String) As String
	DocumentFileName = Left(Doc, Doc.Length - 4)
	'MsgBox(DocumentFileName)
End Function 'DocumentFileName

Function isAsm(ThisDoc As Document) As Boolean
	Debug.Print (ThisDoc.DocumentType)
	If ThisDoc.DocumentType = kAssemblyDocumentObject Then
		isAsm = True
	Else
		isAsm = False
	End If
End Function 'isAsm
