AddReference "C:\Program Files\Autodesk\AutoCAD 2024\Autodesk.AutoCAD.Interop.dll"
AddReference "C:\Program Files\Autodesk\AutoCAD 2024\Autodesk.AutoCAD.Interop.Common.dll"

Imports System.IO
Imports Autodesk.AutoCAD.Interop
Imports Autodesk.AutoCAD.Interop.Common

' Imports acAppSvc = Autodesk.AutoCAD.ApplicationServices
' Imports acDB = Autodesk.AutoCAD.DatabaseServices
' Imports acRT = Autodesk.AutoCAD.Runtime

Sub Main
	
	'On Error Resume Next
	Dim acadApp as AcadApplication
	
	Try
		acadApp = GetObject(, "AutoCAD.Application")   ' attach if already running
	Catch
		' Not running → start it manually
		acadApp = CreateObject("AutoCAD.Application")
	End Try

	
	acadApp.Visible = True
	
	Dim oAsmDoc as Document
	Dim compOcc as ComponentOccurrence
	customPropertySet = ThisDoc.Document.PropertySets.Item("Inventor User Defined Properties")
	
	oAsmDoc = ThisApplication.ActiveEditDocument
	
	If oAsmDoc.FileSaveCounter >= 1 Then
		' Are we in a Assembly or Part Document?
		If oAsmDoc.DocumentType = kAssemblyDocumentObject Or oAsmDoc.DocumentType = kPartDocumentObject Then
			
			'Pull path and File Name, append desired file type, and execute save as.  
			FileName = ThisDoc.Path 'PathAndFileName(False)
			FileNameDWG = Filename & "\" & iProperties.Value("Project", "Part Number") & "-" & iProperties.Value("Project", "Revision Number") & " - " & iProperties.Value("Project", "Description") & ".dwg" 'FileName & " ACAD SIMPLE.DWG"
			'(FileNameDWG)
			ThisDoc.Document.SaveAs(FileNameDWG, True)
			
		Else
		
			MessageBox.Show("This command can only be used in an Assembly or Part.")
			
		End If
		
	Else
	
		MessageBox.Show("File must be saved to continue.", "File Not Saved",MessageBoxButtons.OK,MessageBoxIcon.Error)

	End If
	
	' Dim acDocMgr as Autodesk.AutoCAD.ApplicationServices.DocumentCollection = acadApp.DocumentManager
	
	' Autodesk.AutoCAD.DatabaseServices.DocumentCollectionExtension.Open(acDocMgr, FileNameDWG, False)
	
	acadDoc = acadApp.Documents.Open(FileNameDWG, False)
	
	Dim PropNames as New List(Of String)
	PropNames.Add("Ops")
	PropNames.Add("Width")
	PropNames.Add("Length")
	PropNames.Add("Make-Buy")
	PropNames.Add("Notes")
	PropNames.Add("MaterialDesc")
	PropNames.Add("MaterialNum")
	PropNames.Add("CreateDate")
	PropNames.Add("Designer")
	PropNames.Add("MfgPart#")
	PropNames.Add("RevNum")
	PropNames.Add("PartNumber")
	PropNames.Add("PartDescription")
				
	Dim propPrompt as New List(Of String)
	propPrompt.Add("Ops")	
	propPrompt.Add("Width")
	propPrompt.Add("Length")
	propPrompt.Add("Make-Buy")
	propPrompt.Add("Notes")
	propPrompt.Add("MaterialDesc")
	propPrompt.Add("MaterialNum")
	propPrompt.Add("Creation Date")
	propPrompt.Add("Designer")
	propPrompt.Add("Mfg Part #")
	propPrompt.Add("Rev #")
	propPrompt.Add("Part #")
	propPrompt.Add("Part Description")
	
	Dim propVal as New List(Of String)
	propVal.Add(iProperties.Value("Custom", "OPS"))
	propVal.Add(iProperties.Value("Custom", "WIDTH"))
	propVal.Add(iProperties.Value("Custom", "LENGTH"))
	propVal.Add(iProperties.Value("Custom", "MakeBuy"))
	propVal.Add(iProperties.Value("Custom", "NOTES"))
	propVal.Add(iProperties.Value("Custom", "Material Description"))
	propVal.Add(iProperties.Value("Custom", "Material Number"))
	propVal.Add(iProperties.Value("Project", "Creation Date"))
	propVal.Add(iProperties.Value("Project", "Designer"))
	propVal.Add("")
	propVal.Add(iProperties.Value("Project", "Revision Number"))
	propVal.Add(iProperties.Value("Project", "Part Number"))
	propVal.Add(iProperties.Value("Project", "Description"))
		
		
	Randomize
	Rval = Int(255 * Rnd) +1
	Gval = Int(255 * Rnd) +1
	Bval = Int(255 * Rnd) +1
	
	'acLayCol = Rval , Gval , Bval
	LayerName = iProperties.Value("Project", "Part Number") & "-" & iProperties.Value("Project", "Revision Number") & " - " & iProperties.Value("Project", "Description") '& " - INVENTOR"
	BlockName = LayerName.Replace(" ", "_")

	'AUTOCAD INTERACTION
	'Get Model Space
	acadModel = acadDoc.ModelSpace
	
	'Set ISO view
	acadDoc.SendCommand("-view" & vbCr & "_seiso" & vbCr)
		
	'Create Colors
	Dim color As AcadAcCmColor = acadApp.GetInterfaceObject("AutoCAD.AcCmColor.24")
    color.SetRGB(0 , 0 , 0)
	
	'Add Layers
	TTattLayer = acadDoc.Layers.Add("Attribute_TT")
	TTattLayer.TrueColor = color
	
	'color.SetRGB(Rval , Gval , Bval)
	partLayer = acadDoc.Layers.Add(LayerName)
	color.SetRGB(Rval, Gval, Bval)
	partLayer.TrueColor = color

	'move existing solid(s) to part layer
	For Each entry In acadModel
		entry.Layer = LayerName
	Next
	
	Dim origin as Array = {0#, 0#, 0#}
	
	'Create Block Definition
	'msgbox("block")
	acadDoc.SendCommand("-block" & vbCr & BlockName & vbCr & "0,0,0" & vbCr & "all" & vbCr & vbCr) 'block all objects
	blockTable = acadDoc.Blocks
	blockDef = blockTable.Item(BlockName) 'Add(origin, BlockName)
	
	'create attributes and add to block definition
	Dim Att as Object

	For i = 0 To 12
		att = blockDef.AddAttribute(0.001, acAttributeModeLockPosition, propPrompt(i), origin, PropNames(i), propVal(i))
		'att.Height = 0.001
		att.Visible = True
		att.Constant = False
		att.Layer = "Attribute_TT"
		
		'Write to DWG Properties or future use - drawing.SummaryInfo
		acadDoc.SummaryInfo.AddCustomInfo(PropNames(i), propVal(i))
	Next
	
	For Each entry In acadModel
		entry.Delete
	Next
	
	acadModel.InsertBlock(origin, BlockName, 1#, 1#, 1#, 0) 
	
	TTattLayer.Freeze = True
	TTattLayer.Lock =  True
	
	acadDoc.Save
	
	'AppActivate("AutoCAD Mechanical 2024")
	
	'amscreate - to create AutoCAD Mechanical component


End Sub
