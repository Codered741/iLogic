'Author: Cody Redding
'contact: codered741@gmail.com

'Runs in an Assembly to give all first level components a random color.  
'Procedure:
' Get all first level components
' Create/Switch to new view rep ("Pretty Colors")
' iterate through the components
'  select all instances
'  generate a random color
'  assign color to instances

Sub Main()

	SharedVariable("LogVar") = "Pretty Colors"
	iLogicVB.RunExternalRule("Write SV to Log.iLogicVB")
	
    Dim oAsmDoc As AssemblyDocument = ThisApplication.ActiveDocument
	Dim oAsmDef As AssemblyComponentDefinition = oAsmDoc.ComponentDefinition
	Dim dViewRepMgr As RepresentationsManager = oAsmDef.RepresentationsManager
	Dim dViewReps As DesignViewRepresentations = dViewRepMgr.DesignViewRepresentations
	Dim dMasterViewRep As DesignViewRepresentation = dViewReps.Item("Default")
	Dim vRepName As String = "Pretty Colors" 'name for the new view rep
	Dim dPCViewRep As DesignViewRepresentation 
	Dim oOccs as ComponentOccurrencesEnumerator
	Dim PCVRepOn as Boolean = False
	Dim UsedColors as New List(of Integer)
	Dim BreakLoop as Integer ' used to prevent possible infinite loop
	Dim ColorsCount as Integer = 194
	
	Try
		dPCViewRep = dViewReps.Item(vRepName) 'look for the view rep
	Catch 'assume error means view rep does not exist, and 
		dMasterViewRep.Activate()
		dViewReps.Add(vRepName)
		PCVRepOn = True
	End Try 
	
	IF PCVRepOn = False Then
		dPCViewRep.Activate()
    End If
	
	' Initialize the random number generator and get
    ' the number of render styles defined.
	Randomize
    Dim iColorCount As Long
    iColorCount = oAsmDoc.RenderStyles.Count
	
	Dim BOMDocs As New List(of String)
	
	'get list of part numbers from Structured BOM
	GetDocsFromBOM(ThisApplication.ActiveDocument, BOMDocs)
	
	If BOMDocs.Count > 50 Then
		uCont = MessageBox.Show("This assembly has a large number of parts.  This operation may take some time.  Are you sure you want to continue?", "iLogic", MessageBoxButtons.OKCancel, MessageBoxIcon.Question)
		If uCont = vbCancel Then
			Exit Sub
		End If
	End If
	
	If BOMDocs.Count > ColorsCount Then '194 RAL colors
		uCont = MessageBox.Show("This assembly has more parts than available distinct colors.  The operation will be canceled.  ", "iLogic", MessageBoxButtons.OK, MessageBoxIcon.Error)
		Exit Sub
	End If
	
	
		
	For Each BOMDoc in BOMDocs
		refDoc = ThisApplication.Documents.ItemByName(BOMDoc)
		'If refDoc.DocumentType = kPartDocumentObject Then
			oOccs = oAsmDef.Occurrences.AllReferencedOccurrences(refDoc)
		
			BreakLoop = 0 ' reset for each components
		
		loop1:

			pColor = Int((iColorCount * Rnd) + 1)
			
			If oAsmDoc.RenderStyles.Item(pColor).Name.Contains("RAL") AndAlso Not UsedColors.Contains(pColor) Then
				'Do nothing
			Else
				
				BreakLoop += 1
				
				If BreakLoop > ColorsCount Then
					MessageBox.Show("An error occurred, please check to see that the RAL colors Library is installed. ", "iLogic Error", MessageBoxButtons.OK, MessageBoxIcon.Error)
					Exit Sub
				End If
				
				GoTo loop1 'pick a new color, until an unused RAL color is selected.  
				
			End If
			
			For Each oOcc In oOccs
				oOcc.SetRenderStyle(kOverrideRenderStyle, oAsmDoc.RenderStyles.Item(pColor))
			Next
			
			UsedColors.Add(pColor)
			
		'End If
	Next
	
End Sub 'Main

Sub GetDocsFromBOM(oDoc as Document, ByRef BOMDocs as List(of String))
	
	If oDoc.DocumentType <> kAssemblyDocumentObject Then
		MsgBox("This rule can only be run from an assembly")
		Exit Sub
	End If
	
	Dim oDocBOM As BOM = oDoc.ComponentDefinition.BOM

	oDocBOM.StructuredViewEnabled = True
	oDocBOM.StructuredViewFirstLevelOnly = False
	oDocBOM.PartsOnlyViewEnabled = False
	
	Dim oBOMView as BOMView = oDocBOM.BOMViews.Item("Structured")	
	Dim oBOMRows As BOMRowsEnumerator = oBOMView.BOMRows
	Dim oCompDef As ComponentDefinition
	Dim oPNProp as Inventor.Property
	
	
	For Each oRow as BOMRow in oBOMRows
		
		oCompDef = oRow.ComponentDefinitions.Item(1)
		
		'GetBOMRowDocFile(oRow, BOMDocs)
		
		If oCompDef.Type = 100675072 Then 'exclude Virtual Components
		
			'do nothing
		
		Else

			DocName = oCompDef.Document.FullFileName

			If Not BOMDocs.Contains(DocName) Then
				BOMDocs.Add(DocName)
			End If
			
		End If
		
	Next 
	
	'BOMDocs.Sort()
	
End Sub

' Sub GetBOMRowDocFile(oRow as BOMRow, ByRef BOMDocs as List(of String))
	
	' Dim oCompDef As ComponentDefinition
	
	' 'Add the part number of the current row, for parts that have children
	' oCompDef = oRow.ComponentDefinitions.Item(1)
	
	' If oCompDef.Type = 100675072 Then 'exclude Virtual Components
		' 'do nothing
	' Else

		' DocName = oCompDef.Document.FullFileName

		' If Not BOMDocs.Contains(DocName) Then
			' BOMDocs.Add(DocName)
		' End If
		
	' End If
		
	' If Not oRow.ChildRows Is Nothing Then
	
		' For Each oChildRow as BOMRow in oRow.ChildRows		
			' GetBOMRowDocFile(oChildRow, BOMDocs)
		' Next
		
	' End If
	
' End Sub
