'Adds custom iProperties for Electrical Design use. 
Sub Main()

	SharedVariable("LogVar") = "Electrical Property Add"
	iLogicVB.RunExternalRule("Write SV to Log.iLogicVB")
	
	'Make a ref to active doc
	Dim oDoc As Document
	oDoc = ThisApplication.ActiveDocument

	Dim CTRLSTDProps As New List(Of String)
	Dim CTRLStrParams As New List(Of String)

	'If oDoc.DocumentType = 12291 Then 'kAssemblyDocumentObject
	'		oCompDef = CType(oDoc.ComponentDefinition, AssemblyComponentDefinition)
	'	Else If oDoc.DocumentType = 12290 Then 'kPartDocumentObject
	'		oCompDef = CType(oDoc.ComponentDefinition, PartComponentDefinition)
	'	End If	

	CTRLSTDProps.Add("Heat Load Watts")
	CTRLSTDProps.Add("Max Temp F")
	CTRLSTDProps.Add("FLA")
	CTRLSTDProps.Add("SCCR")
	CTRLSTDProps.Add("UL Number")



	PropAdd(CTRLSTDProps)
	
	'Parameter Setup
	'CTRLStrParams.Add("ProjectNum")

	
	'ParamAdd(CTRLStrParams, "TXT")
	

	'selected components collection
	Dim oSelected As ObjectCollection
	oSelected = ThisApplication.TransientObjects.CreateObjectCollection

	Dim oCount As Integer
	oCount = oDoc.SelectSet.Count

	'Check that at least 1 is selected
	If oCount = 0 Then
		MessageBox.Show("Electrical properties added to active document." & vbLf & "No additional item selected", "iLogic")
		Exit Sub 'bail out
	End If

	'add to Object Collection
	Dim i As Long
	For i = 1 To oCount
		If oDoc.SelectSet.Item(i).Type = _
			ObjectTypeEnum.kComponentOccurrenceObject Then
			oSelected.Add (oDoc.SelectSet.Item(i))
		End If
	Next

	'do stuff to the selected files here:
	Dim Occ As ComponentOccurrence

	'get names item name from collection
	'add iProperties
	For i = 1 To oCount
		oMsg = oMsg & vbLf & oDoc.SelectSet.Item(i).Name
		'PropAdd(CTRLSTDProps)
		Occ=oDoc.SelectSet.Item(i)
		customPropertySet = Occ.Definition.Document.PropertySets.Item("Inventor User Defined Properties")
		For Each prop In CTRLSTDProps
			Try
				iprop = customPropertySet.Item(prop)
			Catch
				' Assume error means not found
				customPropertySet.Add("",prop)
				'iProperties.Value("", prop) = ""
			End Try
			Next
	Next

	MessageBox.Show(oCount _
	& " Component(s) updated." & vbLf & oMsg, "iLogic")

End Sub


Public Sub PropAdd(Props As List(Of String))
	'Init
	Dim oDoc As Document = ThisApplication.ActiveDocument
	customPropertySet = ThisDoc.Document.PropertySets.Item("Inventor User Defined Properties")
	
	For Each prop In Props
		Try
			iprop = customPropertySet.Item(prop)
		Catch
			' Assume error means not found
			customPropertySet.Add("Custom", prop)
			'iProperties.Value("Custom", prop) = ""
		End Try
	Next
End Sub

Public Sub ParamAdd(Params As List(Of String), UnitType As String)
	'Init
	Dim oPartDoc As Document = ThisApplication.ActiveDocument
	Dim oCompDef As ComponentDefinition = oPartDoc.ComponentDefinition
	oMyParameter=oCompDef.Parameters.UserParameters
	
	'Main
	If UnitType = "BOOL" Then	
		For Each pmtr In Params
			Try
				param = Parameter.Param(pmtr)
			Catch
				oMyParameter=oCompDef.Parameters.UserParameters
				oParameter=oMyParameter.AddByValue(pmtr, True, "BOOLEAN")
			End Try
		Next 
	Else If UnitType = "IN" Then
		For Each pmtr In Params
			Try
				param = Parameter.Param(pmtr)
			Catch
				oMyParameter=oCompDef.Parameters.UserParameters
				oParameter=oMyParameter.AddByValue(pmtr, 0 in, UnitsTypeEnum.kInchLengthUnits)
			End Try
		Next 
	Else If UnitType = "TXT"
		For Each pmtr In Params
			Try
				param = Parameter.Param(pmtr)
			Catch
				oMyParameter=oCompDef.Parameters.UserParameters
				oParameter=oMyParameter.AddByValue(pmtr, " ", UnitsTypeEnum.kTextUnits)
				'MultiValue.SetList(pmtr, "Collapsing Tower", "Mariner", "Jetski Launcher", "Masking Curtain", "Seaplane Launcher", "Lakitu Marquee", "Hovering Propeller", "Chain Chomp", "Chandelier", "Airship Propeller", "Small Piranha Plant", "Side Thwomp", "Bounce Pad w/Props")
			End Try
		Next 
	Else If UnitType = "UL" Then
		For Each pmtr In Params
			Try
				param = Parameter.Param(pmtr)
			Catch
				oMyParameter=oCompDef.Parameters.UserParameters
				oParameter=oMyParameter.AddByValue(pmtr, 0 , UnitsTypeEnum.kUnitlessUnits)
			End Try
		Next 
	End If
End Sub
