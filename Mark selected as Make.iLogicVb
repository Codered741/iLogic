SharedVariable("LogVar") = "Mark Selected as Make"
iLogicVB.RunExternalRule("Write SV to Log.iLogicVB")

Dim oDoc As Document = ThisApplication.ActiveDocument
Dim comps As SelectSet = oDoc.SelectSet
Dim comp As ComponentOccurrence


Dim oCompDef As ComponentDefinition = oDoc.ComponentDefinition
oMyParameter=oCompDef.Parameters.UserParameters
'If there are selected components we can do something, otherwise we're done

If comps.count > 0 Then   

numParts = comps.count

	For Each comp In comps
		Try
			param = Parameter.Param(comp.Name, "MB")
		Catch
			comp.Definition.Parameters.UserParameters.AddByValue("MB", True, "BOOLEAN")
		End Try
		Parameter(comp.Name, "MB") = True
		
		Try
			customPropertySet = comp.Definition.Document.PropertySets.Item("Inventor User Defined Properties")
			iprop = customPropertySet.Item("MakeBuy")
		Catch
			' Assume error means not found
			customPropertySet.Add("Custom", "MakeBuy")
			iProperties.Value(comp.Name, "Custom", "MakeBuy") = ""
		End Try
		iProperties.Value(comp.Name, "Custom", "MakeBuy") = "Make"
		
	Next
	
	MessageBox.Show(numParts & " part(s) were successfully changed", "Success")
	
Else
	MessageBox.Show("There are no components selected", "Error")
End If
