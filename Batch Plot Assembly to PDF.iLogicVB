Imports System.IO
Imports System.IO.File
Imports System.Text
Imports My.Computer.FileSystem
'AddReference "C:\Program Files\PDFCreator\PDFCreator.ComWrapper.dll"
'Imports pdfforge.PDFCreator.UI.ComWrapper
'TODO
'Add Vault GET for current assembly
'Add File version check.  (as reference to external rule)

Class Rule
	Sub Main()

		'write to iLogic Log
		SharedVariable("LogVar") = "Batch Plot to qPDF" 
		iLogicVb.RunExternalRule("Write SV to Log.iLogicVB")
			
		Dim oDoc As Document = ThisApplication.ActiveDocument

		'check if active document is an assembly
			If isAsm(oDoc) = False
				MsgBox("Please run from an Assembly")
				Return
			End If

		'get user confirmation on items before starting
		'this will take a while
		Dim usrTimeAck = MessageBox.Show("This rule will find all drawings of parts referenced in the BOM, print them to PDF's and merge them to a single document.  "  _
			& vbLf & "This process can take some time to run, and cannot be stopped once started. " & vbLf & "Please close all related drawings before continuing! ", "Time Warning", MessageBoxButtons.OKCancel, MessageBoxIcon.Warning)
			
		If usrTimeAck = vbCancel Then
			Exit Sub
		End If
		

		
		'confirm getting latest drawings
		Dim usrLatestAck = MessageBox.Show("Would you like to get the latest drawings from Vault? " _ 
			& vbLf & "This can take some time with larger assemblies.  ", "Latest Drawing Warning", MessageBoxButtons.YesNo, MessageBoxIcon.Warning)
			
		If usrLatestAck = vbNo Then	
			Exit Sub
		Else If usrLatestAck = vbYes Then
			iLogicVb.RunExternalRule("Get Latest from Vault.iLogicVB")

		End If

		'confirm comparing the part and drawing versions to be ready for posting
		Dim usrDwgCompareAck = MessageBox.Show("Would you like to check to see if the drawings are up to date?", "Drawing Version Check", MessageBoxButtons.YesNo, MessageBoxIcon.Question)
		
		If usrDwgCompareAck = vbYes Then
			SharedVariable("BatchPlotInvoke") = True
			iLogicVb.RunExternalRule("Check Drawing Update Status.iLogicVB")
			SharedVariable("BatchPlotInvoke") = False
		End If
		
		Dim usrCompareContinueAck = MessageBox.Show("Do you wish to continue plotting drawings?", "Continue batch plot?", MessageBoxButtons.YesNo, MessageBoxIcon.Question)
		
		If usrCompareContinueAck = vbNo Then 
			MsgBox("Run the 'Check Drawing Update Status' rule to update any drawings that are out of date.  ")
			Return
		End If
		
		Dim FileNameMinLong As Integer = 21 'c:/_vaultWIP/Designs/ is 21 characters. 
			
		'begin the Batch Plot process
		Try 
			
			Dim lstDrawings As New List(Of String)
			
			Dim BOMDocs As New List(Of String)
		
			Dim myfrm As New GatherModeForm
				
			'Use ShowDialog so it waits for user / form close before continuing
			myfrm.ShowDialog()
						
			'Dim oResult As CustomForm.CustomDialogResult = myfrm.DialogResult
			Dim oGatherType As String = myfrm.myResult


			If oGatherType = "Bill of Materials"
				GetDocsFromBOM(ThisApplication.ActiveDocument, BOMDocs)
			Else 
				'get list of part numbers from referenced files (TM NEW CODE 2025-07-01)
				Dim oRefDoc As Document
				Dim oNewItem As String
					For Each oRefDoc In oDoc.AllReferencedDocuments
					oNewItem = oRefDoc.FullFileName
					BOMDocs.Add(oNewItem)
					Next
			End If
			
			 Dim oProgressBar As Inventor.ProgressBar
			 oProgressBar = ThisApplication.CreateProgressBar(False, BOMDocs.Count, "Finding Drawings...")

			'Attempt to find a drawing file of the same name as the assembly doc
			RefDwgFullFileName = FindDrawingFilePN(oDoc)
			
			oProgressBar.Message = "Checking for drawing of " & oDoc.FullFileName
			oProgressBar.UpdateProgress
			
			If RefDwgFullFileName.Length > FileNameMinLong Then 
			
				lstDrawings.Add(RefDwgFullFileName)
				
			End If
			
			
			'Dim bDoc as Document
			For Each BOMDoc As String In BOMDocs
				bDoc = ThisApplication.Documents.ItemByName(BOMDoc) 'convert full file name to document object
				
				oProgressBar.Message = "Checking for drawing of " & BOMDoc 'oRefDoc.FullFileName
				oProgressBar.UpdateProgress

				'Attempt to find a drawing file of the same name as the model doc
				RefDwgFullFileName = FindDrawingFilePN(bDoc)

				If RefDwgFullFileName.Length > FileNameMinLong Then 
				
					lstDrawings.Add(RefDwgFullFileName)

				End If
				
			Next
			
			oProgressBar.Close		

			MergePrintDwgs(oDoc.FullFileName, lstDrawings)
	
		Catch Ex As Exception
		
			MsgBox("Main error: " & Ex.Message)
			
		End Try
		
	End Sub 'Main


	Sub CopyPostInfo(doc As Document)
		Dim FinalText As String 
		Dim desPropSet As PropertySet = doc.PropertySets.Item("Design Tracking Properties")
		FinalText = "Job Number: " & desPropSet.Item("Part Number").Value & vbLf & _
						"Kit Name: " & desPropSet.Item("Description").Value & vbLf & _
						"Project Name: " & desPropSet.Item("Project").Value & vbLf & _
						":black_circle:"
		My.Computer.Clipboard.SetText(FinalText)
	End Sub 'CopyPostInfo

	'/////////////////////////////////////// MergePrintDwgs (qpdf implementation 20251028 CPR)
	Private Sub MergePrintDwgs(strFilePath As String, lstDwgsPrint As List(Of String))

		Dim oPath As String = ThisDoc.Path
		Dim oFileName As String = ThisDoc.FileName(False)
		Dim oRevNum As String = iProperties.Value("Project", "Revision Number")
		Dim oDesc As String = iProperties.Value("Project", "Description")
		Dim oPrj As String = iProperties.Value("Project", "Project")

		Dim fullPath As String = oPath & "\" & oFileName & " - " & oPrj & " - " & oDesc & " -REV" & oRevNum & " " & Now.ToString("yyyyMMdd")
		If Len(fullPath) > 254 Then
			MessageBox.Show("Path too long. Using C:\_vaultWIP\Designs\", "Path Warning")
			fullPath = "C:\_vaultWIP\Designs\" & oFileName & " - " & oPrj & " - " & oDesc & " -REV" & oRevNum & " " & Now.ToString("yyyyMMdd")
		End If
		fullPath = fullPath.Replace("/", "")

		Dim tempFolder As String = System.IO.Path.Combine(System.IO.Path.GetTempPath(), "InvPDF_" & Now.ToString("yyyyMMdd_HHmmss"))
		System.IO.Directory.CreateDirectory(tempFolder)

		Dim tempPDFs As New List(Of String)
		Dim oProgressBar As Inventor.ProgressBar = ThisApplication.CreateProgressBar(False, lstDwgsPrint.Count, "Exporting to PDF...")

		Try
			Dim pdfAddIn As Inventor.TranslatorAddIn
			Try
				pdfAddIn = ThisApplication.ApplicationAddIns.ItemById("{0AC6FD96-2F4D-42CE-8BE0-8AEA580399E4}")
				If Not pdfAddIn.Activated Then pdfAddIn.Activate()
			Catch
				MsgBox("PDF Add-In not found. Check Tools > Add-Ins and ensure 'Translator: PDF' is loaded (it should be built-in).")
				Exit Sub
			End Try

			Dim oContext As Inventor.TranslationContext = ThisApplication.TransientObjects.CreateTranslationContext
			oContext.Type = Inventor.IOMechanismEnum.kFileBrowseIOMechanism

			Dim oOptions As Inventor.NameValueMap = ThisApplication.TransientObjects.CreateNameValueMap
			oOptions.Value("All_Color_AS_Black") = 0  ' Full color
			oOptions.Value("Remove_Line_Weights") = 0 ' Keep line weights
			oOptions.Value("Vector_Resolution") = 600 ' Balanced quality/speed
			oOptions.Value("Sheet_Range") = Inventor.PrintRangeEnum.kPrintAllSheets

			Dim oData As Inventor.DataMedium

			For i As Integer = 0 To lstDwgsPrint.Count - 1
				Dim dwgPath As String = lstDwgsPrint(i)
				oProgressBar.Message = "Exporting: " & System.IO.Path.GetFileName(dwgPath)
				oProgressBar.UpdateProgress

				Dim oDoc As DrawingDocument = Nothing
				Try
					'--- Open with DeferUpdates = True, Visible = False ---
					Dim openOpts As Inventor.NameValueMap = ThisApplication.TransientObjects.CreateNameValueMap
					openOpts.Value("DeferUpdates") = True
					openOpts.Value("FastOpen") = True
					openOpts.Value("SkipAllUnresolvedFiles") = True

					oDoc = ThisApplication.Documents.OpenWithOptions(dwgPath, openOpts, False) ' Invisible

					'--- Ensure document is fully loaded ---
					ThisApplication.UserInterfaceManager.DoEvents()
					System.Threading.Thread.Sleep(100) ' Let it settle

					oData = ThisApplication.TransientObjects.CreateDataMedium
					Dim tempPDF As String = tempFolder & "\dwg_" & i & ".pdf"
					oData.FileName = tempPDF

					'--- Export ---
					Try
						pdfAddIn.SaveCopyAs(oDoc, oContext, oOptions, oData)
						tempPDFs.Add(tempPDF)
					Catch ex As Exception
						MessageBox.Show("Failed to export: " & dwgPath & vbCrLf & ex.Message, "Export Failed")
						' Continue with next
					End Try

				Catch ex As Exception
					MessageBox.Show("Failed to open: " & dwgPath & vbCrLf & ex.Message, "Open Failed")
				Finally
					If Not oDoc Is Nothing Then
						Try : oDoc.Close(True) : Catch : End Try
					End If
				End Try
			Next

			'--- Merge with qpdf ---
			Dim qpdfExe As String = "C:\_vaultWIP\Designs\Templates\Library\iLogic\DLL\qpdf.exe"  			
			If Not System.IO.File.Exists(qpdfExe) Then
				MsgBox("qpdf.exe not found at:" & vbCrLf & qpdfExe & vbCrLf & vbCrLf & "Download from: https://github.com/qpdf/qpdf/releases", "Missing qpdf")
				Exit Sub
			End If

			If tempPDFs.Count = 0 Then
				MsgBox("No PDFs to merge.")
				Exit Sub
			End If

			Dim args As String = "--empty --pages"
			For Each p In tempPDFs
				args &= " """ & p & """"
			Next
			args &= " -- """ & fullPath & ".pdf"""

			Dim psi As New System.Diagnostics.ProcessStartInfo
			psi.FileName = qpdfExe
			psi.Arguments = args
			psi.UseShellExecute = False
			psi.CreateNoWindow = True
			psi.RedirectStandardError = True
			psi.RedirectStandardOutput = True
			
			'Check if the file exists, and if it does, test write access.  If it fails, alert the user to close before proceeding.  
			If System.IO.File.Exists(fullPath & ".pdf") Then
				Try
					' Attempt to open the file with write access
					Using fs As New FileStream(filePath, FileMode.Open, FileAccess.Write, FileShare.None)
						' If the FileStream is created successfully, write access exists
					End Using
				Catch ex As Exception
					MessageBox.Show("Could not gain access to the existing file.  Please ensure the file is closed before continuing. ", "File access denied!", MessageBoxButtons.OK, MessageBoxIcon.Warning)
				End Try
			End If
			
			Dim proc As System.Diagnostics.Process
			Try
				proc = System.Diagnostics.Process.Start(psi)
				proc.WaitForExit()
			Catch ex As Exception
				MsgBox("Failed to start qpdf.exe:" & vbCrLf & ex.Message & vbCrLf & vbCrLf & "Install Visual C++ Redistributable (x64):" & vbCrLf & "https://aka.ms/vs/17/release/vc_redist.x64.exe", 0, "qpdf Launch Error")
				Exit Sub
			End Try

			If proc.ExitCode = 0 Then
				'MsgBox("PDF Created:" & vbCrLf & fullPath & ".pdf", 0, "Success")
			Else
				Dim err As String = proc.StandardError.ReadToEnd()
				MsgBox("qpdf failed (Code: " & proc.ExitCode & ")" & vbCrLf & vbCrLf & _
					   "Error: " & err & vbCrLf & vbCrLf & _
					   "Fix: Install Visual C++ Redistributable (x64)", 0 ,  "Merge Failed")
			End If

		Catch ex As Exception
			MsgBox("Unexpected error: " & ex.Message)
		Finally
			For Each f In tempPDFs
				Try : System.IO.File.Delete(f) : Catch : End Try
			Next
			Try : System.IO.Directory.Delete(tempFolder, True) : Catch : End Try
			oProgressBar.Close
		End Try

		Process.Start("explorer.exe", "/select,""" & fullPath & ".pdf""")
	End Sub

	Sub GetDocsFromBOM(oDoc As Document, ByRef BOMDocs As List(Of String))
		
		If oDoc.DocumentType <> kAssemblyDocumentObject Then
			MsgBox("This rule can only be run from an assembly")
			Exit Sub
		End If
		
		Dim oCompDef As AssemblyComponentDefinition = oDoc.ComponentDefinition
		Dim oDocBOM As BOM = oCompDef.BOM

		oDocBOM.StructuredViewEnabled = True
		oDocBOM.StructuredViewFirstLevelOnly = False
		oDocBOM.PartsOnlyViewEnabled = False
		
		Dim oBOMView As BOMView = oDocBOM.BOMViews.Item("Structured")	
		Dim oBOMRows As BOMRowsEnumerator = oBOMView.BOMRows
		'Dim oCompDef As ComponentDefinition
		'Dim oPNProp as Inventor.Property
		
		For Each oRow As BOMRow In oBOMRows
			
				GetBOMRowDocFile(oRow, BOMDocs)
			
		Next 
		
		'BOMDocs.Sort()
		
	End Sub

	Sub GetBOMRowDocFile(oRow As BOMRow, ByRef BOMDocs As List(Of String))
		
		Dim oCompDef As ComponentDefinition
		
		'Add the part number of the current row, for parts that have children
		oCompDef = oRow.ComponentDefinitions.Item(1)
		
		If oCompDef.Type = 100675072 Then 'exclude Virtual Components
			'do nothing
		Else

			DocName = oCompDef.Document.FullFileName

			If Not BOMDocs.Contains(DocName) Then
				BOMDocs.Add(DocName)
			End If
			
		End If
			
		If Not oRow.ChildRows Is Nothing Then
		
			If Not BOMDocs.Contains(DocName) Then
				BOMDocs.Add(DocName)
			End If
		
			For Each oChildRow As BOMRow In oRow.ChildRows		
				GetBOMRowDocFile(oChildRow, BOMDocs)
			Next
			
		End If
		
	End Sub

	Function FindDrawingFilePN(PartOrAssemblyDoc As Document) As String
		Dim fullFilenamePN As String
		fullFilenamePN = PartOrAssemblyDoc.FullFileName
	   
		' Extract the path from the full filename.
		Dim path As String = ThisApplication.DesignProjectManager.ActiveDesignProject.WorkspacePath
		'path = Left$(fullFilenamePN, InStrRev(fullFilenamePN, "\"))

		Dim iProps As PropertySet = PartOrAssemblyDoc.PropertySets.Item("Design Tracking Properties")
		Dim pn = iProps.Item("Part Number")
		
		Dim filename As String = pn.Value

		' Find if the drawing exists.
		Dim drawingFilename As String
		drawingFilename = ThisApplication.DesignProjectManager.ResolveFile(path, filename & ".dwg")
	   
		' Check the result.
		If drawingFilename = "" Then
		   
			' Find if the drawing exists.
			drawingFilename = ThisApplication.DesignProjectManager.ResolveFile(path, filename & ".idw")
	   
			' Return the result.
			If drawingFilename <> "" Then
				Return drawingFilename
			Else
				Return ""
			End If
		Else
			' Return the result.
			 Return drawingFilename
		End If
	End Function 'FindDrawingFilePNN

	Private Sub DwgPrint(PrinterName As String, oPaperSize As Integer)
		Dim oPrintMgr As DrawingPrintManager = ThisApplication.ActiveDocument.PrintManager
		' Get the name of the printer that will be used.
		oPrintMgr.Printer = PrinterName
		
		' Set to print in color.
		oPrintMgr.ColorMode = 13313 'kPrintColorPalette
		
		' Set to print one copies.
		oPrintMgr.NumberOfCopies = 1
		
		' Set to print using landscape orientation.
		oPrintMgr.Orientation = 13570
			'13570 'kLandscapeOrientation
			'13569 'kPortraitOrientation
		
		
		'Set Paper Size
			oPrintMgr.PaperSize = oPaperSize


		
		
		'14338 'kPaperSize11x17
		'oPrintMgr.PaperWidth = 431.8
		'oPrintMgr.PaperHeight = 27.94
		
		' Set to print all sheets.
		oPrintMgr.PrintRange = 14082 'kPrintAllSheets
		
		' Set to print best fit scale
		oPrintMgr.ScaleMode = PrintScaleModeEnum.kPrintBestFitScale
		
		' Submit the print.
		oPrintMgr.SubmitPrint
	End Sub 'DwgPrint

	Private Sub printTestFile()
		Dim ShellObj As Object

		ShellObj = CreateObject("Shell.Application")
		ShellObj.ShellExecute("RUNDLL32.exe", "PRINTUI.DLL,PrintUIEntry /k /n ""PDFCreator""", "", "open", 1)
	End Sub

	Function DocumentFileName(Doc As String) As String
		DocumentFileName = Left(Doc, Doc.Length - 4)
		'MsgBox(DocumentFileName)
	End Function 'DocumentFileName

	Function isAsm(ThisDoc As Document) As Boolean
		Debug.Print (ThisDoc.DocumentType)
		If ThisDoc.DocumentType = kAssemblyDocumentObject Then
			isAsm = True
		Else
			isAsm = False
		End If
	End Function 'isAsm

	Function GetAddinByByName(displayName As String) As Inventor.ApplicationAddIn
		For Each i As Inventor.ApplicationAddIn In ThisServer.ApplicationAddIns
			If i.DisplayName = displayName Then
				Return i
			End If
		Next
		Return Nothing
	End Function
End Class 'Rule

'NEW FORM TM ADDED 2025-08-07:
Public Class GatherModeForm
	Inherits System.Windows.Forms.Form
	
	Public myResult As String = "Bill of Materials"
	
	Public Sub New()
		' This is run when a new instance of the form is created
				
		oForm = Me
		
		With oForm
			' Set up form	
			.FormBorderStyle = FormBorderStyle.FixedToolWindow 'Fixed3D / FixedDialog / FixedSingle / FixedToolWindow / None / Sizable / SizableToolWindow
			'.MaximizeBox = False
			'.MinimizeBox = False
			.StartPosition = FormStartPosition.CenterScreen
			.Width = 600
			.Height = 220
			.TopMost = True
			.Text = "Select Drawing Gather Mode"
			.Name = "Select Drawing Gather Mode"
			
		End With
		
		'Dim oTB As New TextBox()
		'With oTB
			'.Text = "here is some info on how to fill this in" & Chr(10) & "and it goes on 2 lines"
			'.Top = 10
			'.Left = 20
			'.Width = 200
			'.Height = 40
			'.Multiline = True
			'.ReadOnly = True
			'.BorderStyle = None
		'End With
		Dim oRb1 As New RadioButton()
		With oRb1
			.Text = "Bill of Materials" & Chr(10) & "This method will include drawings of BoM items only (Normal, Purchased and Inseperable)"  & Chr(10) & "(This is the 'classic' version of this iLogic script)"
			.Top = 12
			.Width = 560
			.Height = 60
			.Left = 20
		End With
		
		Dim oRb2 As New RadioButton()
		With oRb2
			.Text = "Referenced Files List" & Chr(10) & "This method will include all referenced files with an associated drawing (inc Phantom and Reference)"  & Chr(10) & "(This may include unwanted files - check output packs and remove any stray files manually)"
			.Top = oRb1.Top + 60
			.Width = 560
			.Height = 60
			.Left = 20
		End With
		
		Dim Button1 As New Button()
		With Button1
			.Text = "OK"
			.Top = oRb2.Top + 65
			.Left = 250
			.Enabled = True
		End With		
		
		'Add your Event handler
		AddHandler oRb1.Click, AddressOf BoM_Click
		AddHandler oRb2.Click, AddressOf ReffedFile_Click
		AddHandler Button1.Click, AddressOf SelectButton_Click
'Add Controls
		oForm.Controls.Add(Button1)
		'oForm.Controls.Add(oTB)
		oForm.Controls.Add(oRb1)
		oForm.Controls.Add(oRb2)
		
		'Preselect Bill of Materials Mode
		oRb1.Checked = True
		
	End Sub
  
	Private Sub SelectButton_Click(ByVal sender As System.Object, ByVal E As System.EventArgs)
		sender.parent.Close ' Accesses the form and closes after button click	
	End Sub
	
	Private Sub BoM_Click(ByVal sender As System.Object, ByVal E As System.EventArgs)
		myResult = "Bill of Materials"	
	End Sub
	
	Private Sub ReffedFile_Click(ByVal sender As System.Object, ByVal E As System.EventArgs)
		myResult = "Referenced Files"	
	End Sub
End Class
