SharedVariable("LogVar") = "TAIT Title View Scale"
	iLogicVB.RunExternalRule("Write SV to Log.iLogicVB")

'Overview View Scale
Dim oDoc As ThisApplication.ActiveDocument
Dim oSheets As Sheets = oDoc.Sheets
Dim oTitleSheet As Sheet = oDoc.Sheets.Item(1)
Dim oOverView as DrawingView = oTitleSheet.DrawingViews.Item("Overview")
Dim ViewHorizLoc as Decimal = 


oOverView.SetCenter()

'bourne
' ViewPlaceH = (ThisDrawing.Sheet("Sheet:1").Width /3) + HOverview
' ViewPlaceV = (ThisDrawing.Sheet("Sheet:1").Height/2) + VOverview

' ThisDrawing.Sheet("Sheet:1").View("Overview").SetCenter(ViewPlaceH, ViewPlaceV)
' ThisDrawing.Sheet("Sheet:1").View("Overview").Scale = 1
' viewHeight = ThisDrawing.Sheet("Sheet:1").View("Overview").Height
' ThisDrawing.Sheet("Sheet:1").View("Overview").Scale = (6/ viewHeight)
