'AUTHOR: Cody Redding
'CONTACT: codered741@gmail.com

'"Finish Drawing" rule.  
'completes drawing and prepares for posting.  
' 1. Update drawing date (on part)
' 2. Update Copied iProperties
' 3. Check for 2d Laser/waterjet OS Ops, export DXF if found
' 4. Export PDF
' 5. Save File
' 6. check in file
Sub Main()
	On Error Goto ErrorHandler
	Dim oDoc As Document
	
	SharedVariable("LogVar") = "Finish Drawing"
	iLogicVB.RunExternalRule("Write SV to Log.iLogicVB")
	
	oDoc = ThisApplication.ActiveDocument
	If Not oDoc.DocumentType = kDrawingDocumentObject Then
		MessageBox.Show("Please run this rule from a Drawing file.  ", "Drawing Only Rule", MessageBoxButtons.OK, MessageBoxIcon.Error)
		Exit Sub
	End If
	
	Dim oCommandMgr As CommandManager = ThisApplication.CommandManager
	' Dim oRefDocs As DocumentsEnumerator = oDoc.AllReferencedDocuments
	' Dim oRefDoc As Document = oRefDocs.Item(1)
	' Dim makeDxf AS Boolean = False
	' Dim notDone as Boolean = False
	
	'If the first reference is not a part or assembly, find the first assembly/part in the list.  
	' If oRefDoc.DocumentType <> kAssemblyDocumentObject OrElse oRefDoc.DocumentType <> kPartDocumentObject 
		' For docnum = 2 to oDoc.AllReferencedDocuments.Count ' oRefDoc.DocumentType <> kAssemblyDocumentObject OrElse oRefDoc.DocumentType <> kPartDocumentObject
			' oRefDoc = oDoc.AllReferencedDocuments.Item(docnum)
			' If oRefDoc.DocumentType = kAssemblyDocumentObject OrElse oRefDoc.DocumentType = kPartDocumentObject
				' Exit For
			' End If
		' Next
	' End If
	
	' invDesignInfo = oRefDoc.PropertySets.Item("Design Tracking Properties")
	' oRefCustomProps = oRefDoc.PropertySets.Item("Inventor User Defined Properties")
	'oRefSumProps = oRefDoc.PropertySets.Item("Design Tracking Properties")
	
	'DateProp = invDesignInfo.Item("Creation Time")
	'CheckedDateProp = invDesignInfo.Item("Date Checked")
	'ApprovedDate = invDesignInfo.Item("Engr Date Approved")

	'DateProp.Value = DateString
	'CheckedDateProp.Value = DateString
	'ApprovedDate.Value = DateString

	oCommandMgr.ControlDefinitions.Item("UpdateCopiedModeliPropertiesCmd").Execute2(True)
	oCommandMgr.ControlDefinitions.Item("AppZoomAllCmd").Execute
	' Try
		' prop = oRefCustomProps.Item("OPS")
		' If oRefCustomProps.Item("OPS").Value.Contains("OS") Then
			' iLogicVb.RunExternalRule("Export and Attach DXF")
		' End If
	' Catch
		' MessageBox.Show("Please check the Smart Part Config for this Part/Assembly.  The 'OPS' Parameter is missing. ", "Missing Parameter")
		' 'Exit Sub
		' notDone = True
	' End Try
	'iLogicVb.RunExternalRule("Export and Attach PDF")
	
	oDoc.Update
	oDoc.Sheets.Item(1).Activate
	oDoc.Save
	
	If notDone = False Then
		oCommandMgr.ControlDefinitions.Item("VaultCheckinTop").Execute
	Else
		MessageBox.Show("An Error occurred.  Please try again.", "iLogic", MessageBoxButtons.OK, MessageBoxIcon.Warning)
		Exit Sub
	End If
	
	ThisApplication.ActiveDocument.Close
	
ErrorHandler:
	notDone = True
	Resume Next
	
End Sub
